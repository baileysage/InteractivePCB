/***************************************************************************************************
                                         USAGE DECLERATION
***************************************************************************************************/
#usage "en: Interactive PCB Data Generator ULP\n"
           "Implements a generator that extracts needed data from a board file \n"
           "and creates the JavaScript JSON variable that is needed for interactive PCB \n"
           "to function\n\n"
           "Usage: RUN ipcb.ulp\n"
           "Author: Sean Alling"
/**************************************************************************************************/

/**************************************************************************************************/
/********************                    GLOBAL DEFINITIONS                    ********************/
/**************************************************************************************************/

    int PROTOCOL_VERSION = 2;

    /*Function to get path to folder with project which is now opened.*/
    string get_project_path()
    {
      if (board)     board(B)     return(filedir(B.name));
      if (schematic) schematic(S) return(filedir(S.name));
      if (library)   library(L)   return(filedir(L.name));
    }



    int Result = 0;

    int setting_DarkMode = 0;
    int setting_HighlightFirstPin = 0;
    int settings_HidePlacedParts = 0;
    int setting_CombineValues = 0;
    int setting_RenderingBOMLayout = 0;
    int setting_AdditionalTable = 0;
    string setting_OutputDirectory = get_project_path();
    string selectionOptions_bomLayoutSelections[]        = { "BOM Only", "BOM Left, PCB Right", "BOM Top, PCB Bottom", "PCB Only" };
    string selectionOptions_bomLayoutSelectionsMapping[] = { "BOM", "LR", "TB", "PCB" };
    string selectionOptions_TableSelections[]        = {"None", "Trace Table", "Test Point Table", "Layer Table"};
    string selectionOptions_TableSelectionsMapping[] = {"None", "Tr", "Tp", "Lr"};
    string setting_AdditionalCheckBoxes = "";
    string setting_AdditionalPartAttributes = "";
    Result = dlgDialog("interactive PCB Export")
    {
        dlgGroup("iPCB Settings")
        {
            dlgHBoxLayout
            {
                dlgGroup("Rendering")
                {
                    dlgCheckBox("&Dark mode"          , setting_DarkMode);
                    dlgCheckBox("&Highlight first pin", setting_HighlightFirstPin);
                    dlgCheckBox("&Hide placed parts", settings_HidePlacedParts);
                    dlgStretch(1);
                }
                dlgGroup("Additional BOM Settings")
                {
                    dlgCheckBox("&Combine BOM values"     , setting_CombineValues);
                    dlgLabel("Additional Check boxes");
                    dlgStringEdit(setting_AdditionalCheckBoxes);
                    dlgLabel("Additional Part Attributes");
                    dlgStringEdit(setting_AdditionalPartAttributes);
                }
            }


            dlgGroup("Layout Settings")
            {
                dlgHBoxLayout
                {
                    dlgVBoxLayout
                    {
                        dlgLabel("&Default BOM & PCB Layout");
                        dlgListBox(selectionOptions_bomLayoutSelections, setting_RenderingBOMLayout);
                    }
                    dlgVBoxLayout
                    {
                        dlgLabel("&Default Additional Table");
                        dlgListBox(selectionOptions_TableSelections    , setting_AdditionalTable);
                    }
                }
            }
        }
        dlgHBoxLayout
        {
            dlgPushButton("&Output Directory")
            {
                setting_OutputDirectory = dlgDirectory("Select directory", get_project_path());
            }
            dlgLabel(setting_OutputDirectory,1);
        }
        dlgPushButton("&Execute")
        {
           dlgAccept();
        }
    };

    string outputFileName = setting_OutputDirectory + "/" +"pcbdata.json";

    string layerNames[];


    // Eagle color codes are ARGB
    // iPCB expects them in RGBA.
    char hex_characters[]={'0','1','2','3','4','5','6','7','8','9','A','B','C','D','E','F'};
    string PalletColorToHTMLString(int colorCode_ARGB)
    {
        int A = ((colorCode_ARGB >> 24) & 0xFF);
        int R = ((colorCode_ARGB >> 16) & 0xFF);
        int G = ((colorCode_ARGB >>  8) & 0xFF);
        int B = ((colorCode_ARGB >>  0) & 0xFF);

        string str="#";
        str += hex_characters[(R>>4) & 0xF];
        str += hex_characters[(R>>0) & 0xF];
        str += hex_characters[(G>>4) & 0xF];
        str += hex_characters[(G>>0) & 0xF];
        str += hex_characters[(B>>4) & 0xF];
        str += hex_characters[(B>>0) & 0xF];
        str += hex_characters[(A>>4) & 0xF];
        str += hex_characters[(A>>0) & 0xF];


        return str;
    }

    /*
    DESCRIPTION: Scans a string and replaces douple quotes (") with a space character. This is needed
                 so that the resulting JSON file is valid. Without this check the resulting JSON
                 could include double quotes embedded in a  part and the resulting JSON is invalid
                 which will make iPCB not work.
    */
    string removeDoubleQuote(string passedString)
    {
        for (int i = 0; passedString[i]; ++i)
        {
            if(passedString[i] == '\"')
            {
                passedString[i] = ' ';
            }
        }
        return passedString;
    }
/**************************************************************************************************/

/**************************************************************************************************/
/********************                    COMMON DEFINITIONS                    ********************/
/**************************************************************************************************/

    /******************** SEGMENT DEFINITIONS ********************/

    /********** PATH DEFINITIONS **********/
    void Print_Segment_Path_Line(string layerName, real x0, real y0, real x1, real y1, real width)
    {
        printf(   "{\"type\":\"line\",\"layer\":\"%s\",\"x0\":%5.5f,\"y0\":%5.5f,\"x1\":%5.5f,\"y1\":%5.5f,\"width\":%5.5f}"
                , layerName
                , x0
                , y0
                , x1
                , y1
                , width
              );
    }

    void Print_Segment_Path_Arc(string layerName, real x0, real y0, real radius, real angle0, real angle1, real width)
    {
        printf(   "{\"type\":\"arc\",\"layer\":\"%s\",\"cx0\":%5.5f,\"cy0\":%5.5f,\"radius\":%5.5f,\"angle0\":%5.5f,\"angle1\":%5.5f,\"width\":%5.5f,\"direction\":\"clockwise\"}"
                , layerName
                , x0
                , y0
                , radius
                , angle0
                , angle1
                , width
            );
    }

    /********** POLYGONS DEFINITIONS **********/
    void Print_Segment_Path_Polygon(void)
    {
        //<POLYGON>          ::= "{" "\"type\"" ":" "\"polygon\"" "," "\"layer\":" <STRING> "," "\"positive\"" ":" <POLYGON_DIRECTION> "," "\"segments\"" ":" "[" <PATHS> "]" "}"
    }

    /********** VIA DEFINITIONS **********/

    void Print_Segment_Via(string viaType, string layerName, real x, real y, real diameter, real drill)
    {
        printf(   "{\"type\":\"%s\",\"layer\":\"%s\",\"x\":%5.5f,\"y\":%5.5f,\"diameter\":%5.5f,\"drill\":%5.5f}"
                , viaType
                , layerName
                , x
                , y
                , diameter
                , drill
              );
    }

    void Print_Segment_VIA_Round(string layerName,real x, real y, real diameter, real drill)
    {
        Print_Segment_Via("via_round", layerName, x, y, diameter, drill);
    }

    void Print_Segment_VIA_Square(string layerName,real x, real y, real diameter, real drill)
    {
        Print_Segment_Via("via_square", layerName, x, y, diameter, drill);
    }

    void Print_Segment_VIA_Octogon(string layerName, real x, real y, real diameter, real drill)
    {
        Print_Segment_Via("via_octagon", layerName, x, y, diameter, drill);
    }

    void Print_BoundingBox(real x0, real y0, real x1, real y1, real angle)
    {
        printf(   "\"bounding_box\":{\"x0\":%5.5f,\"y0\":%5.5f,\"x1\":%5.5f,\"y1\":%5.5f,\"angle\":%5.5f}"
                , x0
                , y0
                , x1
                , y1
                , angle
              );
    }
/**************************************************************************************************/

/**************************************************************************************************/
/********************                   METADATA DEFINITIONS                   ********************/
/**************************************************************************************************/
    void Print_Metadata_ProtocolVersion(int versionNumber)
    {
        printf("\"protocol_version\":%u", versionNumber);
    }

    void Print_Metadata_CompanyName(UL_BOARD B)
    {
            /*
                Iterate over the board attributes looking for 'COMPANY'. If this attribute exists
                it returns the value set for 'COMPANY' if set, otherwise returns an empty string.
            */
            string companyName = "";
            B.attributes(A)
            {
                if( (A.name == "COMPANY") )
                {
                    companyName = A.value;
                }
            }
            printf("\"company\":\"%s\"", companyName);
    }

    void Print_Metadata_ProjectRevision(UL_BOARD B)
    {
        /*
            Iterate over the board attributes looking for 'REV' or 'REVISION'. If this attribute exists
            it returns the value set for 'REV' or 'REVISION' if set, otherwise returns an empty string.
        */
        string revision = "";
        B.attributes(A)
        {
            if( (A.name == "REV") || (A.name == "REVISION"))
            {
                revision = A.value;
            }
        }
        printf("\"revision\":\"%s\"", revision);
    }

    void Print_Metadata_ECAD(void)
    {
        printf("\"ecad\":\"EAGLE\"");
    }

    void Print_Metadata_ProjectName(string pcbFileName)
    {
        // Used to hold the project name
        string projectName[];
        // filename(xxx) removes the directory part of the string if it exists.
        // strsplit splits its input string by looking for '.' and puts the result in projectName
        int n = strsplit(projectName, filename(pcbFileName), '.');
        // The first element (at index 0), contains the filename.
        printf("\"project_name\":\"%s\"",projectName[0]);
    }

    void Print_Metadata_Date(void)
    {
        printf("\"date\":\"%s\"", t2string(time(), "Uyyyy-MM-dd hh:mm:ss"));
    }

    void Print_Metadata_NumberParts_Top(UL_BOARD B)
    {
        int partCount = 0;
        B.elements(E)
        {
            if(!E.mirror)
            {
                partCount = partCount + 1;
            }
        }
        printf("\"top\":%u", partCount);
    }

    void Print_Metadata_NumberParts_Bottom(UL_BOARD B)
    {
        int partCount = 0;
        B.elements(E)
        {
            if(E.mirror)
            {
                partCount = partCount + 1;
            }
        }
        printf("\"bottom\":%u", partCount);
    }

    void Print_Metadata_NumberParts(UL_BOARD B)
    {
        printf("\"number_parts\":{");
        Print_Metadata_NumberParts_Top(B);
        printf(",");
        Print_Metadata_NumberParts_Bottom(B);
        printf("}");
    }

    void Print_Metadata( void )
    {
        board(B)
        {
            /*
                Print the metadata information to file.
            */
            printf("\"metadata\":{");
            Print_Metadata_ProtocolVersion(PROTOCOL_VERSION);
            printf(",");
            Print_Metadata_ECAD();
            printf(",");
            Print_Metadata_CompanyName(B);
            printf(",");
            Print_Metadata_ProjectName(B.name);
            printf(",");
            Print_Metadata_ProjectRevision(B);
            printf(",");
            Print_Metadata_Date();
            printf(",");
            Print_Metadata_NumberParts(B);
            printf("}");
        }
    }
/**************************************************************************************************/

/**************************************************************************************************/
/********************                     BOARD DEFINITIONS                    ********************/
/**************************************************************************************************/
    void Print_Board_Traces_PCB_Trace(UL_SIGNAL S)
    {
        printf("{\"name\":\"%s\",\"segments\":[", S.name);
        int printedOnce = 0;
        S.wires(W)
        {
            if(printedOnce == 1)
            {
                printf(",");
            }
            if(W.arc)
            {
                // According to eagle documentation, output is always clockwise.
                Print_Segment_Path_Arc(layerNames[W.layer] ,u2mm(W.arc.xc), u2mm(W.arc.yc),  u2mm(W.arc.radius),  W.arc.angle1,  W.arc.angle2,  u2mm(W.width));
            }
            else
            {
                Print_Segment_Path_Line(layerNames[W.layer], u2mm(W.x1), u2mm(W.y1), u2mm(W.x2), u2mm(W.y2), u2mm(W.width));
            }
            printedOnce = 1;
        }
        S.vias(V)
        {
            if(printedOnce == 1)
            {
                printf(",");
            }
            if(V.shape[LAYER_TOP] ==  VIA_SHAPE_SQUARE)
            {
                Print_Segment_VIA_Square(layerNames[LAYER_VIAS],u2mm(V.x), u2mm(V.y), u2mm(V.diameter[LAYER_TOP]), u2mm(V.drill));
            }
            else if(V.shape[LAYER_TOP] ==  VIA_SHAPE_ROUND)
            {
                Print_Segment_VIA_Round(layerNames[LAYER_VIAS],u2mm(V.x), u2mm(V.y), u2mm(V.diameter[LAYER_TOP]), u2mm(V.drill));
            }
            // must be octagon
            else
            {
                Print_Segment_VIA_Octogon(layerNames[LAYER_VIAS],u2mm(V.x), u2mm(V.y), u2mm(V.diameter[LAYER_TOP]), u2mm(V.drill));
            }
            printedOnce = 1;
        }

        //S.polygons(P)
        //{
        //    if(printedOnce == 1)
        //    {
        //        printf(",");
        //    }
        //    Print_Segment_Path_Polygon(P);
        //    printedOnce = 1;
        //}

        printf("]");
        printf("}");
    }

    void Print_Board_Traces_PCB_Traces(void)
    {
        board(B)
        {
            int once_signal = 0;
            B.signals(S)
            {
                if(once_signal == 1)
                {
                    printf(",");
                }
                Print_Board_Traces_PCB_Trace(S);
                once_signal = 1;
            }
        }
    }

    void Print_Board_Traces_PCB_Layer(UL_LAYER L)
    {
        printf("{\"name\":\"%s\",\"paths\":[",L.name);
        board(B)
        {
            int once = 0;
            B.texts(T)
            {
                if(T.layer == L.number)
                {
                    T.wires(W)
                    {
                        if(once == 1)
                        {
                            printf(",");
                        }
                        if(W.arc)
                        {
                            Print_Segment_Path_Arc(L.name, u2mm(W.arc.xc), u2mm(W.arc.yc),  u2mm(W.arc.radius), W.arc.angle1, W.arc.angle2, u2mm(W.width));
                        }
                        else
                        {
                            Print_Segment_Path_Line(L.name, u2mm(W.x1), u2mm(W.y1), u2mm(W.x2), u2mm(W.y2), u2mm(W.width));
                        }
                        once = 1;
                    }
                }
            }

            B.wires(W)
            {
                if(W.layer == L.number)
                {
                    if(once == 1)
                    {
                        printf(",");
                    }
                    if(W.arc)
                    {
                        Print_Segment_Path_Arc(L.name , u2mm(W.arc.xc), u2mm(W.arc.yc), u2mm(W.arc.radius), W.arc.angle1, W.arc.angle2, u2mm(W.width));
                    }
                    else
                    {
                        Print_Segment_Path_Line(L.name, u2mm(W.x1),  u2mm(W.y1), u2mm(W.x2), u2mm(W.y2), u2mm(W.width));
                    }
                    once = 1;
                }
            }

            // Print text associated and shapes associated to components.
            // Need to iterate over all elements if they exist on the layer.
            B.elements(E)
            {
                // Outputs text that is still attached to part (not smashed).
                E.footprint.circles(C)
                {
                    if(C.layer == L.number)
                    {
                         //TODO: Current not supported
                    }
                }

                // Outputs text that is still attached to part (not smashed).
                E.footprint.polygons(P)
                {
                    if(P.layer == L.number)
                    {
                        // Using contour loop variable to get the eagle calculate boundaries for the polygon.
                        P.contours(C)
                        {
                            //TODO: Current not supported
                        }
                    }
                }

                // Outputs text that is still attached to part (not smashed).
                E.footprint.texts(T)
                {
                    if(T.layer == L.number)
                    {

                        T.wires(W)
                        {
                            if(once == 1)
                            {
                                printf(",");
                            }
                            if(W.arc)
                            {
                                Print_Segment_Path_Arc(L.name ,u2mm(W.arc.xc), u2mm(W.arc.yc),  u2mm(W.arc.radius),  W.arc.angle1,  W.arc.angle2,  u2mm(W.width));
                            }
                            else
                            {
                                Print_Segment_Path_Line(L.name, u2mm(W.x1), u2mm(W.y1), u2mm(W.x2), u2mm(W.y2), u2mm(W.width));
                            }
                            once = 1;
                        }
                    }
                }

                E.footprint.wires(W)
                {
                    if(W.layer == L.number)
                    {
                            if(once == 1)
                            {
                                printf(",");
                            }
                            if(W.arc)
                            {
                                Print_Segment_Path_Arc(L.name ,u2mm(W.arc.xc), u2mm(W.arc.yc),  u2mm(W.arc.radius),  W.arc.angle1,  W.arc.angle2,  u2mm(W.width));
                            }
                            else
                            {
                                Print_Segment_Path_Line(L.name, u2mm(W.x1), u2mm(W.y1), u2mm(W.x2), u2mm(W.y2), u2mm(W.width));
                            }
                            once = 1;
                    }
                }

                // Outputs text smashed for part.
                E.texts(T)
                {
                    if(T.layer == L.number)
                    {
                        T.wires(W)
                        {
                            if(once == 1)
                            {
                                printf(",");
                            }
                            if(W.arc)
                            {
                                Print_Segment_Path_Arc(L.name ,u2mm(W.arc.xc), u2mm(W.arc.yc),  u2mm(W.arc.radius),  W.arc.angle1,  W.arc.angle2,  u2mm(W.width));
                            }
                            else
                            {
                                Print_Segment_Path_Line(L.name, u2mm(W.x1), u2mm(W.y1), u2mm(W.x2), u2mm(W.y2), u2mm(W.width));
                            }
                            once = 1;
                        }
                    }
                }
            }

        }
        printf("]");
        printf("}");
    }

    void Print_Board_Traces_PCB_Layers(void)
    {
        board(B)
        {
            int firstLayer = 1;
            B.layers(L)
            {
                if(L.used)
                {
                    if(!firstLayer)
                    {
                        printf(",");
                    }
                    Print_Board_Traces_PCB_Layer(L);
                    firstLayer = 0;
                }
            }
        }
    }

    void Print_Board_Shape(void)
    {
        board(B)
        {
            Print_BoundingBox(u2mm(B.area.x1), u2mm(B.area.y1), u2mm(B.area.x2), u2mm(B.area.y2), 0);
        }
    }

    void Print_Board_Traces(void)
    {
        printf("\"traces\":[");
        Print_Board_Traces_PCB_Traces();
        printf("]");
    }

    void Print_Board_Layers(void)
    {
        printf("\"layers\":" "[");
        Print_Board_Traces_PCB_Layers();
        printf("]");
    }

    void Print_Board_Data( void )
    {
        printf("\"board\":{");
        Print_Board_Shape();
        printf(",");
        Print_Board_Traces();
        printf(",");
        Print_Board_Layers();
        printf("}");
    }
/**************************************************************************************************/

/**************************************************************************************************/
/********************                      PART DEFINITIONS                    ********************/
/**************************************************************************************************/
    int Print_Part_Pad_IsPin1(UL_CONTACT C)
    {
        if(C.name=="1")
        {
           return 1;
        }
        else
        {
            return 0;
        }
    }

    real Print_Part_Pad_Drill(UL_CONTACT C)
    {
        if(!C.smd)
        {
            return u2mm(C.pad.drill);
        }
        else
        {
            return 0;
        }
    }

    void Print_Part_Pad_SMD(UL_CONTACT C)
    {
        printf(   "{\"pin1\":%u,\"type\":\"%s\",\"angle\":%5.5f,\"x\":%5.5f," "\"y\":%5.5f,\"dx\":%5.5f,\"dy\":%5.5f,\"drill\":%5.5f}"
                , Print_Part_Pad_IsPin1(C)
                , "smd"
                , C.smd.angle
                , u2mm(C.smd.x)
                , u2mm(C.smd.y)
                , u2mm(C.smd.dx)
                , u2mm(C.smd.dy)
                , Print_Part_Pad_Drill(C)
              );
    }

    void Print_Part_Pad_Rectangle(UL_CONTACT C)
    {
        printf(   "{\"pin1\":%u,\"type\":\"%s\",\"angle\":%5.5f,\"x\":%5.5f," "\"y\":%5.5f,\"dx\":%5.5f,\"dy\":%5.5f,\"drill\":%5.5f}"
                , Print_Part_Pad_IsPin1(C)
                , "rect"
                , C.pad.angle
                , u2mm(C.pad.x)
                , u2mm(C.pad.y)
                , u2mm(C.pad.diameter[LAYER_TOP])
                , u2mm(C.pad.diameter[LAYER_TOP])
                , Print_Part_Pad_Drill(C)
              );
    }

    void Print_Part_Pad_Oblong(UL_CONTACT C)
    {
        printf(   "{\"pin1\":%u,\"type\":\"%s\",\"angle\":%5.5f,\"x\":%5.5f,\"y\":%5.5f,\"diameter\":%5.5f,\"elongation\":%d,\"drill\":%5.5f}"
                , Print_Part_Pad_IsPin1(C)
                , "oblong"
                , C.pad.angle
                , u2mm(C.pad.x)
                , u2mm(C.pad.y)
                , u2mm(C.pad.diameter[LAYER_TOP])
                , C.pad.elongation
                , Print_Part_Pad_Drill(C)
              );
    }

    void Print_Part_Pad_Round(UL_CONTACT C)
    {
        printf(   "{\"pin1\":%u,\"type\":\"%s\",\"angle\":%5.5f,\"x\":%5.5f,\"y\":%5.5f,\"diameter\":%5.5f,\"drill\":%5.5f}"
                , Print_Part_Pad_IsPin1(C)
                , "round"
                , C.pad.angle
                , u2mm(C.pad.x)
                , u2mm(C.pad.y)
                , u2mm(C.pad.diameter[LAYER_TOP])
                , u2mm(C.pad.drill)
              );
    }

    void Print_Part_Pad_Octagon(UL_CONTACT C)
    {
        printf(   "{\"pin1\":%u,\"type\":\"%s\",\"angle\":%5.5f,\"x\":%5.5f,\"y\":%5.5f,\"diameter\":%5.5f,\"drill\":%5.5f}"
                , Print_Part_Pad_IsPin1(C)
                , "octagon"
                , C.pad.angle
                , u2mm(C.pad.x)
                , u2mm(C.pad.y)
                , u2mm(C.pad.diameter[LAYER_TOP])
                , u2mm(C.pad.drill)
              );
    }

    void Print_Part_Pad_Offset(UL_CONTACT C)
    {
        printf(   "{\"pin1\":%u,\"type\":\"%s\",\"angle\":%5.5f,\"x\":%5.5f,\"y\":%5.5f,\"diameter\":%5.5f,\"elongation\":%d,\"drill\":%5.5f}"
                , Print_Part_Pad_IsPin1(C)
                , "offset"
                , C.pad.angle
                , u2mm(C.pad.x)
                , u2mm(C.pad.y)
                , u2mm(C.pad.diameter[LAYER_TOP])
                , C.pad.elongation
                , u2mm(C.pad.drill)
              );
    }

    void Print_Part_Package_Pad(UL_CONTACT C)
    {
        if(C.smd)
        {
            Print_Part_Pad_SMD(C);
        }
        else
        {
            if(C.pad.shape[LAYER_TOP] == PAD_SHAPE_SQUARE)
            {
                Print_Part_Pad_Rectangle(C);
            }
            else if(C.pad.shape[LAYER_TOP] == PAD_SHAPE_ROUND)
            {
                Print_Part_Pad_Round(C);
            }
            else if(C.pad.shape[LAYER_TOP] == PAD_SHAPE_OCTAGON)
            {
                Print_Part_Pad_Octagon(C);
            }
            else if(C.pad.shape[LAYER_TOP] == PAD_SHAPE_LONG)
            {
                Print_Part_Pad_Oblong(C);
            }
            else if(C.pad.shape[LAYER_TOP] == PAD_SHAPE_OFFSET)
            {
                Print_Part_Pad_Offset(C);
            }
        }
    }

    void Print_Part_Package_Pads(UL_ELEMENT E)
    {
        int firstPad = 1;
        printf("\"pads\": [");
        E.package.contacts(C)
        {
            if (!firstPad)
            {
                printf(",");
            }
            Print_Part_Package_Pad(C);
            firstPad = 0;
        }
        printf("]");
    }

    void Print_Part_Package_BoundingBox(UL_ELEMENT E)
    {
        int min_x = E.x;
        int max_x = E.x;

        int min_y = E.y;
        int max_y = E.y;

        int dx = 0;
        int dy = 0;

        int dx_tmp = 0;
        int dy_tmp = 0;

        E.package.contacts(C)
        {
            if(min_x > C.x)
            {
                min_x = C.x;
            }

            if(max_x < C.x)
            {
                max_x = C.x;
            }

            if(min_y > C.y)
            {
                min_y = C.y;
            }

            if(max_y < C.y)
            {
                max_y = C.y;
            }



            if(C.smd)
            {
                dx_tmp = (C.smd.dx)/2 + (C.smd.dx)/4;
                dy_tmp = (C.smd.dy)/2 + (C.smd.dy)/4;
            }
            else
            {
                if (    (C.pad.shape[LAYER_TOP] == PAD_SHAPE_SQUARE)
                     || (C.pad.shape[LAYER_TOP] == PAD_SHAPE_ROUND)
                     || (C.pad.shape[LAYER_TOP] == PAD_SHAPE_OCTAGON)
                    )
                {
                    dx_tmp = (C.pad.diameter[LAYER_TOP])/2 + (C.pad.diameter[LAYER_TOP])/8;
                    dy_tmp = dx_tmp;
                }
                else if (   (C.pad.shape[LAYER_TOP] == PAD_SHAPE_LONG)
                         || (C.pad.shape[LAYER_TOP] == PAD_SHAPE_OFFSET)
                        )
                {
                    dx_tmp = (C.pad.diameter[LAYER_TOP]);
                    dy_tmp = dx_tmp;
                }
            }


            if(dx < dx_tmp)
            {
                dx = dx_tmp;
            }

            if(dy < dy_tmp)
            {
                dy = dy_tmp;
            }
        }

        Print_BoundingBox(u2mm(min_x-dx), u2mm(min_y-dy), u2mm(max_x+dx), u2mm(max_y+dy), E.angle);
    }

    void Print_Part_Name(string name)
    {
        printf("\"name\":\"%s\"", name);
    }

    void Print_Part_Value(string value)
    {
        printf("\"value\":\"%s\"", value);
    }

    void Print_Part_Package(UL_ELEMENT E)
    {
        printf("\"package\":{");
        Print_Part_Package_Pads(E);
        printf(",");
        Print_Part_Package_BoundingBox(E);
        printf("}");
    }

    void Print_Part_Attributes(UL_ELEMENT E)
    {
        printf("\"attributes\":[");
        int firstAttribute = 1;
        E.attributes(A)
        {
            if(!firstAttribute)
            {
                printf(",");
            }
            printf("{\"name\":\"%s\",\"value\":\"%s\"}",removeDoubleQuote(A.name),removeDoubleQuote(A.value));
            firstAttribute = 0;
        }
        if(!firstAttribute)
        {
            printf(",");
        }
        printf("{\"name\":\"%s\",\"value\":\"%s\"}","footprint",E.footprint.name);
        firstAttribute = 0;
        printf("]");
    }

    void Print_Part_Location(UL_ELEMENT E)
    {
        printf("\"location\":");
        if(!E.mirror)
        {
            printf("\"F\"");
        }
        else
        {
            printf("\"B\"");
        }
    }

    void Print_Part(UL_ELEMENT E)
    {
        printf("{");
        Print_Part_Name(E.name);
        printf(",");
        Print_Part_Value(E.value);
        printf(",");
        Print_Part_Package(E);
        printf(",");
        Print_Part_Attributes(E);
        printf(",");
        Print_Part_Location(E);
        printf("}");
    }

    void Print_Parts(void)
    {
        int firstPart = 1;
        board(B)
        {
            B.elements(E)
            {
                if(!firstPart)
                {
                    printf(",");
                }
                Print_Part(E);
                firstPart = 0;
            }
        }
    }

    void Print_Parts_Data(void)
    {
        printf("\"parts\":" "[");
        Print_Parts();
        printf("]");
    }
/**************************************************************************************************/

/**************************************************************************************************/
/********************                    TEST POINT DEFINITIONS                ********************/
/**************************************************************************************************/
void Print_TestPoints()
{
    printf("\"test_points\": [");

    board(B)
    {
        int firstTestPoint = 1;
        B.elements(E)
        {
            E.package.contacts(C)
            {
                if(C.name == "TP")
                {
                    if(!firstTestPoint)
                    {
                        printf(",");
                    }
                    printf( "{\"name\":\"%s\",\"description\":\"%s\",\"expected\":\"%s\"}"
                            ,C.name
                            ,E.attribute["DESCRIPTION"]
                            ,E.attribute["EXPECTED"]
                          );
                    firstTestPoint = 0;
                }
            }
        }
    }
    printf("]");
}
/**************************************************************************************************/

/**************************************************************************************************/
/********************                  CONFIGURATION DEFINITIONS               ********************/
/**************************************************************************************************/
    void ConfigurationParameter_String(string category, string name, string value)
    {
        printf( "{\"category\":\"%s\",\"name\":\"%s\",\"value\":\"%s\"}"
                    ,category
                    ,name
                    ,value
                  );
    }

    void ConfigurationParameter_Integer(string category, string name, int value)
    {
        printf( "{\"category\":\"%s\",\"name\":\"%s\",\"value\":\"%d\"}"
                    ,category
                    ,name
                    ,value
                  );
    }

    void ConfigurationParameter_Real(string category, string name, real value)
    {
        printf( "{\"category\":\"%s\",\"name\":\"%s\",\"value\":\"%5.5f\"}"
                    ,category
                    ,name
                    ,value
                  );
    }

    void Print_Configuration_Data()
    {
        printf("\"configuration\": [");

        board(B)
        {
            int firstLayer = 1;
            B.layers(L)
            {
                if(L.used)
                {
                    if(!firstLayer)
                    {
                        printf(",");
                    }
                    ConfigurationParameter_String("color", L.name ,PalletColorToHTMLString(palette(L.color)));
                    firstLayer = 0;
                }
            }
        }

        // Now print config data based on user preferences

        printf(",");
        ConfigurationParameter_Integer("setting" , "dark_mode"           , setting_DarkMode);
        printf(",");
        ConfigurationParameter_Integer("setting" , "hight_first_pin"     , setting_HighlightFirstPin);
        printf(",");
        ConfigurationParameter_Integer("setting" , "hide_placed_parts"   , settings_HidePlacedParts);
        printf(",");
        ConfigurationParameter_Integer("setting" , "combine_values"      , setting_CombineValues);
        printf(",");
        ConfigurationParameter_String("setting"  , "bom_pcb_layout"      , selectionOptions_bomLayoutSelectionsMapping[setting_RenderingBOMLayout]);
        printf(",");
        ConfigurationParameter_String("setting"  , "additional_table"    , selectionOptions_TableSelectionsMapping[setting_AdditionalTable]);
        printf(",");
        ConfigurationParameter_String("setting"  , "bom_checkboxes"      , setting_AdditionalCheckBoxes);
        printf(",");
        ConfigurationParameter_String("setting"  , "bom_part_attributes" , setting_AdditionalPartAttributes);
        printf("]");
    }
/**************************************************************************************************/



if (Result != -1)
{
    output(outputFileName,"wt")
    {
        board(B)
        {
            B.layers(L)
            {
                layerNames[L.number] = L.name;
            }
        }

        printf("var pcbdata =  {");
        Print_Metadata();
        printf(",");
        Print_Board_Data();
        printf(",");
        Print_Parts_Data();
        printf(",");
        Print_TestPoints();
        printf(",");
        Print_Configuration_Data();
        printf("}");
    }
}
